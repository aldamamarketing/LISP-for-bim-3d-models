;; TMD - ARQ-DOOR-Insert
;; Comando descriptivo semántico para insertar puertas paramétricas en muros en 2D.

(defun c:ARQ-DOOR-Insert ()
  (princ "\n[LispCentral] Comando ejecutado: ARQ-DOOR-Insert")
  (setvar "USERS1" "ARQ-DOOR-Insert:active")
  (princ "\nSeleccione la pared en el punto donde desea colocar la puerta...")
  (princ)
)
