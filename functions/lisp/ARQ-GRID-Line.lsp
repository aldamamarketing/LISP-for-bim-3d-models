;; TMD - ARQ-GRID-Line
;; Comando descriptivo semántico para trazar líneas de ejes individuales en 2D.

(defun c:ARQ-GRID-Line ()
  (princ "\n[LispCentral] Comando ejecutado: ARQ-GRID-Line")
  (setvar "USERS1" "ARQ-GRID-Line:active")
  (princ "\nSeleccione el punto de inicio para la línea de eje...")
  (princ)
)
