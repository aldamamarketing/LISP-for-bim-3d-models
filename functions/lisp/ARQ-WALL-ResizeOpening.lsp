;; TMD - ARQ-WALL-ResizeOpening
;; Comando descriptivo semántico para cambiar las dimensiones de un vano (puerta/ventana) existente.

(defun c:ARQ-WALL-ResizeOpening ()
  (princ "\n[LispCentral] Comando ejecutado: ARQ-WALL-ResizeOpening")
  (setvar "USERS1" "ARQ-WALL-ResizeOpening:active")
  (princ "\nSeleccione la puerta o ventana que desea redimensionar...")
  (princ)
)
