;; TMD - ARQ-GRID-Axes
;; Comando descriptivo semántico para generar rejillas de ejes paramétricas en 2D.

(defun c:ARQ-GRID-Axes ()
  (princ "\n[LispCentral] Comando ejecutado: ARQ-GRID-Axes")
  (setvar "USERS1" "ARQ-GRID-Axes:active")
  (princ "\nConfigure las distancias de ejes X/Y en la paleta de propiedades...")
  (princ)
)
