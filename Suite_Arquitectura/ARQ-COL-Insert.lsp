;; TMD - ARQ-COL-Insert
;; Comando descriptivo semántico para insertar columnas en 2D.

(defun c:ARQ-COL-Insert ()
  (princ "\n[LispCentral] Comando ejecutado: ARQ-COL-Insert")
  (setvar "USERS1" "ARQ-COL-Insert:active")
  (princ "\nSeleccione la intersección de ejes para colocar la columna...")
  (princ)
)
