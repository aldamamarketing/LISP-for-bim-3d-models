;; TMD - ARQ-SYM-Level
;; Comando descriptivo semántico para colocar marcas de niveles de piso dinámica.

(defun c:ARQ-SYM-Level ()
  (princ "\n[LispCentral] Comando ejecutado: ARQ-SYM-Level")
  (setvar "USERS1" "ARQ-SYM-Level:active")
  (princ "\nSeleccione la ubicación para la etiqueta de nivel de piso...")
  (princ)
)
