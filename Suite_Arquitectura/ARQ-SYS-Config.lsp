;; TMD - ARQ-SYS-Config
;; Comando descriptivo semántico para configurar la suite de arquitectura 2D.

(defun c:ARQ-SYS-Config ()
  (princ "\n[LispCentral] Comando ejecutado: ARQ-SYS-Config")
  (setvar "USERS1" "ARQ-SYS-Config:active")
  (princ "\nAbriendo panel de configuraciones en la paleta de propiedades...")
  (princ)
)
