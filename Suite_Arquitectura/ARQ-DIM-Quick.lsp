;; TMD - ARQ-DIM-Quick
;; Comando descriptivo semántico para acotación rápida interior de espacios.

(defun c:ARQ-DIM-Quick ()
  (princ "\n[LispCentral] Comando ejecutado: ARQ-DIM-Quick")
  (setvar "USERS1" "ARQ-DIM-Quick:active")
  (princ "\nHaga clic dentro del cuarto para acotar su contorno interior...")
  (princ)
)
