;; TMD - ARQ-WIN-Insert
;; Comando descriptivo semántico para insertar ventanas paramétricas en muros en 2D.

(defun c:ARQ-WIN-Insert ()
  (princ "\n[LispCentral] Comando ejecutado: ARQ-WIN-Insert")
  (setvar "USERS1" "ARQ-WIN-Insert:active")
  (princ "\nSeleccione la pared en el punto donde desea colocar la ventana...")
  (princ)
)
