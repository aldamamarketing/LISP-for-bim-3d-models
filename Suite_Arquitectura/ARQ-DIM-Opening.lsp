;; TMD - ARQ-DIM-Opening
;; Comando descriptivo semántico para acotar muros y vanos de forma continua.

(defun c:ARQ-DIM-Opening ()
  (princ "\n[LispCentral] Comando ejecutado: ARQ-DIM-Opening")
  (setvar "USERS1" "ARQ-DIM-Opening:active")
  (princ "\nSeleccione la pared o tramo a acotar...")
  (princ)
)
