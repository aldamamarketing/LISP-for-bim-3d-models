;; TMD - ARQ-WALL-Trim
;; Comando descriptivo semántico para limpiar intersecciones de muros en T, L o cruz.

(defun c:ARQ-WALL-Trim ()
  (princ "\n[LispCentral] Comando ejecutado: ARQ-WALL-Trim")
  (setvar "USERS1" "ARQ-WALL-Trim:active")
  (princ "\nSeleccione la unión de muros que desea limpiar de solapes...")
  (princ)
)
