;; TMD - ARQ-WALL-FromAxis
;; Comando descriptivo semántico para generar muros automáticamente a partir de ejes.

(defun c:ARQ-WALL-FromAxis ()
  (princ "\n[LispCentral] Comando ejecutado: ARQ-WALL-FromAxis")
  (setvar "USERS1" "ARQ-WALL-FromAxis:active")
  (princ "\nSeleccione las líneas de eje para convertirlas en muros...")
  (princ)
)
