;; TMD - ARQ-WALL-MoveOpening
;; Comando descriptivo semántico para mover puertas/ventanas sanando la pared anterior.

(defun c:ARQ-WALL-MoveOpening ()
  (princ "\n[LispCentral] Comando ejecutado: ARQ-WALL-MoveOpening")
  (setvar "USERS1" "ARQ-WALL-MoveOpening:active")
  (princ "\nSeleccione la puerta o ventana que desea mover...")
  (princ)
)
