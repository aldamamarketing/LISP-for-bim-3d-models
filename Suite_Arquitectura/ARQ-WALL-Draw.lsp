;; TMD - ARQ-WALL-Draw
;; Comando descriptivo semántico para dibujar muros interactivos en 2D.

(defun c:ARQ-WALL-Draw ()
  (princ "\n[LispCentral] Comando ejecutado: ARQ-WALL-Draw")
  (setvar "USERS1" "ARQ-WALL-Draw:active")
  (princ "\nIndique puntos en pantalla para trazar el muro doble...")
  (princ)
)
